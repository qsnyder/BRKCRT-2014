module person-model {
  namespace "http://com/example/personmodel";
  prefix person-model;
  container person {
    leaf name {type string;}
    leaf age {type uint32;}
    leaf favorite-color {type string;}
}}
